Module-simple-test DEFINITIONS AUTOMATIC TAGS ::= BEGIN

  Simple-choice-t ::= CHOICE {
    sleep Sleep-time-t,
    eat Food-t
  }

  Food-t ::= ENUMERATED {
    carrot,
    apple,
    banana
  }

  Sleep-time-t ::= SEQUENCE {
    begin Time-t,
    end Time-t
  }

  Time-t ::= SEQUENCE {
    -- 24 h format --
    hour INTEGER(0..23),
    -- 1 h == 60 min --
    minute INTEGER(0..59)
  }

END
