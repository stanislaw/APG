Module-sequence-test DEFINITIONS AUTOMATIC TAGS ::= BEGIN

  Sleep-time-t ::= SEQUENCE {
    begin Time-t,
    end Time-t
  }

  Time-t ::= SEQUENCE {
    -- [h] 24 h format --
    hour INTEGER(0..23),
    -- [min] 1 h == 60 min --
    minute INTEGER(0..59)
  }

END
