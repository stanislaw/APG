Module-tmtc DEFINITIONS AUTOMATIC TAGS ::= BEGIN

  -- 16 bit, 0x0000 to 0xFFFF --
  Uint16-t ::= INTEGER(0..65535)
  -- 32 bit, 0x00000000 to 0xFFFFFFFF --
  Uint32-t ::= INTEGER(0..4294967295)
  -- 64 bit --
  Uint64-t ::= INTEGER(0..18446744073709551615)

  -- 0.00% to 100.00% --
  Percent ::= REAL(0.00 .. 100.00)
  Load ::= REAL(0.00 .. 30.00)

  Tm-tc ::= CHOICE {
    sandbox-ping Sandbox-ping,
    sandbox-hk-pc Sandbox-hk-pc
  }

  Sandbox-ping ::= SEQUENCE {
    -- 0x0888 --
    primary-header Ccsds-primary-header
      (WITH COMPONENTS {
        packet-version-number (0),
        packet-identification (WITH COMPONENTS {
          packet-type-is-cmd (FALSE),
          sec-hdr-flag-is-present (TRUE),
          application-process-identifier (136)
        })
      }),
    secondary-header Secondary-header
  }

  Sandbox-hk-pc ::= SEQUENCE {
    -- 0x0899 --
    primary-header Ccsds-primary-header
      (WITH COMPONENTS {
        packet-version-number (0),
        packet-identification (WITH COMPONENTS {
          packet-type-is-cmd (FALSE),
          sec-hdr-flag-is-present (TRUE),
          application-process-identifier (153)
        })
      }),
    secondary-header Secondary-header,
    payload Payload-sandbox-hk-pc
  }

  Payload-sandbox-hk-pc ::= SEQUENCE {
    cpu Percent,
    load1 Load,
    load5 Load,
    load15 Load,
    -- [byte] --
    total-ram Uint64-t,
    -- [byte] --
    free-ram Uint64-t,
    -- [byte] --
    free-swap Uint64-t
  }

  Ccsds-primary-header ::= SEQUENCE {
    -- 3bit, 0b000 to 0b111 --
    packet-version-number INTEGER(0..7),
    packet-identification Packet-identification,
    packet-sequence-control Packet-sequence-control,
    packet-data-length Uint16-t
  }

  Packet-identification ::= SEQUENCE {
    -- 1: cmd, 0: tlm --
    packet-type-is-cmd BOOLEAN,
    -- 1: present, 0: absent --
    sec-hdr-flag-is-present BOOLEAN,
    -- 11 bit, 0b00000000000 to 0b11111111111 --
    application-process-identifier INTEGER(0..2047)
  }

  Packet-sequence-control ::= SEQUENCE {
    sequence-flags Sequence-flag,
    -- 14 bit, 0b00000000000000 to 0b11111111111111 --
    packet-sequence-count INTEGER(0..16383)
  }

  -- 2 bit, 0b00 to 0b11 --
  Sequence-flag ::= ENUMERATED {
    continuation-packet-in-sequence (0),
    first-packet-in-sequence (1),
    last-packet-in-sequence (2),
    complete-packet (3)
  }

  Secondary-header ::= SEQUENCE {
    seconds Uint32-t,
    subsecs Uint16-t
  }
  
END
