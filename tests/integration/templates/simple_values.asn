Module-simple-values DEFINITIONS AUTOMATIC TAGS ::= BEGIN

  -- 16 bit, 0x0000 to 0xFFFF --
  Uint16-t ::= INTEGER(0..65535)
  -- 32 bit, 0x00000000 to 0xFFFFFFFF --
  Uint32-t ::= INTEGER(0..4294967295)
  -- 64 bit --
  Uint64-t ::= INTEGER(0..18446744073709551615)

  -- [%] 0.00% to 100.00% --
  Percent ::= REAL(0.00 .. 100.00)

END
