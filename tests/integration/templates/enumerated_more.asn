Module-enumeration-test-more DEFINITIONS AUTOMATIC TAGS ::= BEGIN

  Food-t ::= ENUMERATED {
    -- a carrot --
    carrot,
    apple,
    banana
  }

  Hobbies-t ::= ENUMERATED {
    diving,
    swimming,
    sleeping,
    biking
  }

END
