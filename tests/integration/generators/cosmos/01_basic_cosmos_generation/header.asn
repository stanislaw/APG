-- CCSDS TM/TC header --
Module-tmtc-header DEFINITIONS AUTOMATIC TAGS ::= BEGIN

  IMPORTS Uint3, Uint11, Uint14, Uint16-t, Uint32-t FROM Module-simple-types;

  -- primary header --
  Ccsds-primary-header ::= SEQUENCE {
    packet-version-number Uint3,
    packet-identification Packet-identification,
    packet-sequence-control Packet-sequence-control,
    -- length of the packet --
    packet-data-length Uint16-t
  }

  Packet-identification ::= SEQUENCE {
    packet-type-is-cmd BOOLEAN,
    sec-hdr-flag-is-present BOOLEAN,
    application-process-identifier Uint11
  }

  Packet-sequence-control ::= SEQUENCE {
    sequence-flags Sequence-flag,
    packet-sequence-count Uint14
  }

  Sequence-flag ::= ENUMERATED {
    continuation-packet-in-sequence (0),
    first-packet-in-sequence (1),
    last-packet-in-sequence (2),
    complete-packet (3)
  }

  Secondary-header ::= SEQUENCE {
    -- [sec] --
    seconds Uint32-t,
     -- [ms] --
    subsecs Uint16-t,
    -- Spares --
    spare-2-align Uint32-t
  }

END
