Module-gnc DEFINITIONS AUTOMATIC TAGS ::= BEGIN

  IMPORTS Cfe-tlm-header FROM Module-cfe-headers
          Real-range FROM Module-simple-types;

  -- GNC_DATA_MID gnc_DataTlm_t (0x08A0) --
  Gnc-data-tlm ::= SEQUENCE {
      header Cfe-tlm-header (WITH COMPONENTS {
      primary (WITH COMPONENTS {
        packet-version-number (0),
        packet-identification (WITH COMPONENTS {
          packet-type-is-cmd (FALSE),
          sec-hdr-flag-is-present (TRUE),
          application-process-identifier (160)
        })
      })
    }),
    payload Payload-gnc-data-tlm
  }

  Payload-gnc-data-tlm ::= SEQUENCE {
    -- ENDIANNESS(LITTLE) [m] --
    pos Real-range,
    -- ENDIANNESS(LITTLE) [m/s] --
    vel Real-range,
    -- ENDIANNESS(LITTLE) [m/s^2] --
    acc Real-range,
    -- ENDIANNESS(LITTLE) --
    p Real-range,
    -- ENDIANNESS(LITTLE) --
    i Real-range,
    -- ENDIANNESS(LITTLE) --
    d Real-range,
    -- ENDIANNESS(LITTLE) [N] --
    thrust Real-range
  }

END
