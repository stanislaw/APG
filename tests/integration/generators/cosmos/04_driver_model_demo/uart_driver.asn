Module-uart-driver DEFINITIONS AUTOMATIC TAGS ::= BEGIN

  IMPORTS Cfe-tlm-header FROM Module-cfe-headers
          Real-range FROM Module-simple-types;

  -- UART_DRIVER_UART_0_READ_MID uart_driver_ReadTlm_t (0x08D0) --
  Uart-driver-uart0-read-tlm ::= SEQUENCE {
    header Cfe-tlm-header (WITH COMPONENTS {
      primary (WITH COMPONENTS {
        packet-version-number (0),
        packet-identification (WITH COMPONENTS {
          packet-type-is-cmd (FALSE),
          sec-hdr-flag-is-present (TRUE),
          application-process-identifier (208)
        })
      })
    }),
    payload Payload-uart-driver
  }

  -- UART_DRIVER_UART_1_READ_MID uart_driver_ReadTlm_t (0x08D1) --
  Uart-driver-uart1-read-tlm ::= SEQUENCE {
    header Cfe-tlm-header (WITH COMPONENTS {
      primary (WITH COMPONENTS {
        packet-version-number (0),
        packet-identification (WITH COMPONENTS {
          packet-type-is-cmd (FALSE),
          sec-hdr-flag-is-present (TRUE),
          application-process-identifier (209)
        })
      })
    }),
    payload Payload-uart-driver
  }

  Payload-uart-driver ::= SEQUENCE {
    -- [m] TODO String --
    raw Real-range
  }

END
