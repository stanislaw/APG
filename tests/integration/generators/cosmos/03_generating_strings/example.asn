Module-example DEFINITIONS AUTOMATIC TAGS ::= BEGIN

  Digits ::= INTEGER(0..9)

  Simple-choice ::= SEQUENCE {
    sleep Sleep-time,

    -- select two food --
    eat SEQUENCE (SIZE (2)) OF Food,
    visible-string IA5String (SIZE (128)),
    numeric-string NumericString (SIZE (129)),

    -- your 5 digit zip code --
    zip-code SEQUENCE (SIZE (5)) OF Digits
  }

  Food ::= ENUMERATED {
    carrot,
    apple,
    banana
  }

  Sleep-time ::= SEQUENCE {
    begin Time,
    end Time
  }

  Time ::= SEQUENCE {
    -- [h] --
    hour INTEGER(0..23),
    -- [min] --
    minute INTEGER(0..59)
  }

END
