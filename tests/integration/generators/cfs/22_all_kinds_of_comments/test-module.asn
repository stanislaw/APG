-- Module test-module comment --
Module-test-module DEFINITIONS AUTOMATIC TAGS ::= BEGIN

  -- Import comment used. --
  IMPORTS
    -- Import comment ignored. --
    Simple-types-1-type1, Simple-types-1-type2 FROM Module-test-simple-types1
    Simple-types-2-type1, Simple-types-2-type2 FROM Module-test-simple-types2;

  -- Test-seq comment --
  Test-module-test-seq ::= SEQUENCE {
    -- testseq1 field1 comment --
    test-module-test-seq-1-field-1 Test-module-type-seq-1,
    -- testseq1 field2 comment --
    test-module-test-seq-1-field-2 Test-module-type-seq-2
  }


  -- Type-seq-1 comment --
  Test-module-type-seq-1 ::= SEQUENCE {
    -- ts1 field1 comment --
    test-module-type-seq-1-field-1 Simple-types-1-type1,
    -- ts1 field2 comment --
    test-module-type-seq-1-field-2 Simple-types-1-type2
  }

  -- Type-seq-2 comment --
  Test-module-type-seq-2 ::= SEQUENCE {
    -- ts2 field1 comment --
    test-module-type-seq-2-field-1 Simple-types-2-type1,
    -- ts2 field2 comment --
    test-module-type-seq-2-field-2 Simple-types-2-type2
  }

END
