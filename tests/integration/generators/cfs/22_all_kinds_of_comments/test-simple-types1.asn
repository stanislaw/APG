-- Module test-simple-types1 comment --
Module-test-simple-types1 DEFINITIONS AUTOMATIC TAGS ::= BEGIN

  -- int 0-11 comment --
  Simple-types-1-type1 ::= INTEGER(0..11)
  -- int 0-12 comment --
  Simple-types-1-type2 ::= INTEGER(0..12)

END
